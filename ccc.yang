module ccc {
  namespace "http://com/example/ccc";
  prefix ccc;

  import ietf-inet-types {
    prefix inet;
  }
  import tailf-common {
    prefix tailf;
  }
  import tailf-ncs {
    prefix ncs;
  }
  import junos {
    prefix junos;
  }

  augment /ncs:services {

    list ccc {
      description "This is an RFS skeleton service";

      key name;
      leaf name {
      tailf:info "Unique circuit cross connect id between two routers";
        type uint32 {
          range "512..1024";
        }
      }

      uses ncs:service-data;
      ncs:servicepoint ccc-servicepoint;

      tailf:action self-test {
        tailf:info "Perform self-test of the service";
        tailf:actionpoint ccc-self-test;
        output {
          leaf success {
            type boolean;
          }
          leaf message {
            type string;
            description
              "Free format message.";
          }
        }
      }
      list device-if {
        tailf:info "device-interface combination";
        min-elements 2;
        max-elements 2;
        key device;

        leaf device {
          tailf:info "CCC router";
          type leafref {
            path "/ncs:devices/ncs:device/ncs:name";
          }
        }
 
        leaf interface {
          tailf:info "CCC interface on device";
          type leafref {
            // admin@ncs% show | display xpath | display prefixes
            // path "/ncs:devices/ncs:device[ncs:name='vsrx01']/ncs:config/junos:configuration/junos:interfaces/junos:interface/junos:name";
            // path "deref(../device)/../ncs:config/junos:configuration/junos:interfaces/junos:interface/junos:name";
            path "/ncs:devices/ncs:device[ncs:name=current()/../device]/ncs:config/junos:configuration/junos:interfaces/junos:interface/junos:name";
          }
          // An interface we want to configure as ccc must have encapsulation vlan-ccc and vlan-tagging should be enabled
          // /ncs:devices/ncs:device[ncs:name='vsrx01']/ncs:config/junos:configuration/junos:interfaces/junos:interface[junos:name='ge-0/0/2']/junos:vlan-tagging
          // /ncs:devices/ncs:device[ncs:name='vsrx01']/ncs:config/junos:configuration/junos:interfaces/junos:interface[junos:name='ge-0/0/2']/junos:encapsulation vlan-ccc
          must "/ncs:devices/ncs:device[ncs:name=current()/../device]/ncs:config/junos:configuration/junos:interfaces/junos:interface[junos:name=current()]/junos:encapsulation = 'vlan-ccc' and /ncs:devices/ncs:device
[ncs:name=current()/../device]/ncs:config/junos:configuration/junos:interfaces/junos:interface[junos:name=current()]/junos:vlan-tagging" {
             error-message "Only vlan-ccc interfaces with encapsulation type vlan-tagging can be selected";
          }
        }
      }
    }
  }
}
